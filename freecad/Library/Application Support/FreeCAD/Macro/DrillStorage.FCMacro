import math
import Draft

App.activeDocument().addObject('Sketcher::SketchObject', 'DrillSketch')
App.activeDocument().DrillSketch.Placement = App.Placement(App.Vector(0.000000, 0.000000, 0.000000), App.Rotation(0.000000, 0.000000, 0.000000, 1.000000))
App.activeDocument().DrillSketch.MapMode = "Deactivated"


radius = 65
textHeight = 10
fudge = 1

outer =   [
      [ 0.2280, ""       ],
      [ 0.2210, ""       ],
      [ 0.2130, "1/4-28" ],
      [ 0.2090, ""       ],
      [ 0.2055, ""       ],
      [ 0.2040, ""       ],
      [ 0.2010, "1/4-20" ],
      [ 0.1990, ""       ],
      [ 0.1960, ""       ],
      [ 0.1935, ""       ],
      [ 0.1910, ""       ],
      [ 0.1890, ""       ],
      [ 0.1850, "12-32"  ],
      [ 0.1820, "12-28"  ],
      [ 0.1800, ""       ],
      [ 0.1770, "12-24"  ],
      [ 0.1730, ""       ],
      [ 0.1695, ""       ],
      [ 0.1660, ""       ],
      [ 0.1610, ""       ],
      [ 0.1590, "10-32"  ],
      [ 0.1570, "10-30"  ],
      [ 0.1540, ""       ],
      [ 0.1520, ""       ],
      [ 0.1495, "10-24"  ],
      [ 0.1470, ""       ],
      [ 0.1440, ""       ],
      [ 0.1405, "8-40"   ],
      [ 0.1360, "8-32,36"],
      [ 0.1285, ""       ],
      [ 0.1200, ""       ],
      [ 0.1160, ""       ],
      [ 0.1130, "6-40"   ],
      [ 0.1110, "6-36"   ],
      [ 0.1100, ""       ],
      [ 0.1065, "6-32"   ]
   ]   

def stringat(a,r,s):
   x = math.cos(a) * r
   y = math.sin(a) * r
   angle = math.degrees(a);
   ss = Draft.make_shapestring(String=s, FontFile="/Volumes/homes/rcvn/Desktop/Monaco.ttf", Size=2.5, Tracking=0.0)
   ss.Justification = u"Middle-Left"
   ss.Placement = App.Placement(App.Vector(x,y,0),App.Rotation(App.Vector(0,0,1),angle))
      
angle  = 0
turn = math.radians(10)
line = math.radians(2.5)

for i in outer:
    inches = i[0]
    mm = inches * 25.4
    x = math.cos(angle) * radius
    y = math.sin(angle) * radius
    App.ActiveDocument.DrillSketch.addGeometry(Part.Circle(App.Vector(x,y,0.0),App.Vector(0.0, 0.0, 1.0), mm/2))
    stringat(angle,75,"{:.4f} in".format(inches))
    stringat(angle+line,75,"{:.2f} mm".format(mm))
    angle = angle + turn



# ss = Draft.make_shapestring(String="0.2280\n123", FontFile="/Volumes/homes/rcvn/Desktop/Monaco.ttf", Size=2.5, Tracking=0.0)
# ss.Justification = u"Middle-Left"
# ss.Placement = App.Placement(App.Vector(70,0,0),App.Rotation(App.Vector(0,0,1),0))
# # ss.AttachmentSupport = None
# # Draft.autogroup(ss)
# 
# ss = Draft.make_shapestring(String="this", FontFile="/Volumes/homes/rcvn/Desktop/Monaco.ttf", Size=3.0, Tracking=0.0)
# ss.Justification = u"Middle-Center"
# ss.Placement = App.Placement(App.Vector(0,70,0),App.Rotation(App.Vector(0,0,1),180))
# # ss.AttachmentSupport = None
# # Draft.autogroup(ss)
